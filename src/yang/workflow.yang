module workflow {

  namespace "http://example.com/workflow";
  prefix workflow;

  import ietf-inet-types {
    prefix inet;
  }
  import tailf-common {
    prefix tailf;
  }
  import tailf-ncs {
    prefix ncs;
  }

  description
    "Bla bla...";

  revision 2016-01-01 {
    description
      "Initial revision.";
  }

///////// Plan states ////////
  identity type {
    description "plan component type";
    base ncs:plan-component-type;
  }

  identity step1 {
    description "Created Loopback IF";
    base ncs:plan-state;
  }

  identity verify_IF {
    description "Check IF is created";
    base ncs:plan-state;
  }

  identity step2 {
    description "Set BGP";
    base ncs:plan-state;
  }

  identity post_check {
    description "Confirmed everything is done!";
    base ncs:plan-state;
  }

  ///////// Plan states ////////

  list workflow {
    description "This is an RFS skeleton service";

    key name;
    leaf name {
      tailf:info "Unique service id";
      tailf:cli-allow-range;
      type string;
    }

    uses ncs:plan-data;
    uses ncs:service-data;
    ncs:servicepoint workflow-servicepoint;

    // may replace this with other ways of refering to the devices.
    leaf dev1 {
      type leafref {
        path "/ncs:devices/ncs:device/ncs:name";
      }
    }
    leaf dev2 {
      type leafref {
        path "/ncs:devices/ncs:device/ncs:name";
      }
    }

    // replace with your own stuff here
    leaf dev1-loop {
      type inet:ipv4-address;
    }
    leaf dev2-loop {
      type inet:ipv4-address;
    }
    leaf asnum {
      type uint16{
        range "100..300"{
          error-message "AS number must be within 100 to 300";
              }
      }
    }
    leaf step1 {
      type boolean;
      default false;
    }
    leaf verify_IF {
      type boolean;
      default false;
    }
    leaf step2 {
      type boolean;
      default false;
    }
    leaf post_check {
      type boolean;
      default false;
    }

    // Action YANG
    tailf:action checkBGP {
      tailf:info "Check BGP stetus";
      tailf:actionpoint wf-checkBGP-point;
      output{
        leaf dev1 {
          type string;
        }
        leaf dev2 {
          type string;
        }
        leaf result {
            type boolean;
        }
      }
    }

    tailf:action pingLoopback {
      tailf:info "Check Loopback reachability";
      tailf:actionpoint wf-pingLoopback-point;
      output{
        leaf dev1 {
          type string;
        }
        leaf dev2 {
          type string;
        }
        leaf result {
            type boolean;
        }
      }
    }
  }
}
